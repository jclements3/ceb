/* GENERATED by sysml_trade.py -- do not hand-edit */
package CinvaRamTrade {
    private import ScalarValues::*;
    private import ISQ::*;
    private import SI::*;
    private import USCustomaryUnits::*;
    private import TradeStudies::*;
    private import CinvaRamExample::*;

    part v_dcam1250_tside500 :> cinvaRam {
        :>> dCam = 1.25 ['in'];
        :>> tSide = 0.5 ['in'];
        :>> peakHandleForce = 98.1 [lbf];
        :>> peakEjectForce  = 92.0 [lbf];
        :>> steelMass       = 247.6 [lb];
        :>> minMargin       = 0.0603;   // Cam pin, bending
        :>> interferences   = 0;
        :>> functionalFails = 0;
    }
    part v_dcam1250_tside625 :> cinvaRam {
        :>> dCam = 1.25 ['in'];
        :>> tSide = 0.625 ['in'];
        :>> peakHandleForce = 98.1 [lbf];
        :>> peakEjectForce  = 92.0 [lbf];
        :>> steelMass       = 264.7 [lb];
        :>> minMargin       = 0.0603;   // Cam pin, bending
        :>> interferences   = 0;
        :>> functionalFails = 0;
    }
    part v_dcam1375_tside500 :> cinvaRam {
        :>> dCam = 1.375 ['in'];
        :>> tSide = 0.5 ['in'];
        :>> peakHandleForce = 98.1 [lbf];
        :>> peakEjectForce  = 92.0 [lbf];
        :>> steelMass       = 248.1 [lb];
        :>> minMargin       = 0.0675;   // Side plate, bending
        :>> interferences   = 0;
        :>> functionalFails = 0;
    }
    part v_dcam1375_tside625 :> cinvaRam {
        :>> dCam = 1.375 ['in'];
        :>> tSide = 0.625 ['in'];
        :>> peakHandleForce = 98.1 [lbf];
        :>> peakEjectForce  = 92.0 [lbf];
        :>> steelMass       = 265.2 [lb];
        :>> minMargin       = 0.0750;   // Handle, bending at the bridge
        :>> interferences   = 0;
        :>> functionalFails = 0;
    }
    part v_dcam1500_tside500 :> cinvaRam {
        :>> dCam = 1.5 ['in'];
        :>> tSide = 0.5 ['in'];
        :>> peakHandleForce = 98.1 [lbf];
        :>> peakEjectForce  = 92.0 [lbf];
        :>> steelMass       = 248.6 [lb];
        :>> minMargin       = 0.0675;   // Side plate, bending
        :>> interferences   = 0;
        :>> functionalFails = 0;
    }
    part v_dcam1500_tside625 :> cinvaRam {
        :>> dCam = 1.5 ['in'];
        :>> tSide = 0.625 ['in'];
        :>> peakHandleForce = 98.1 [lbf];
        :>> peakEjectForce  = 92.0 [lbf];
        :>> steelMass       = 265.8 [lb];
        :>> minMargin       = 0.0750;   // Handle, bending at the bridge
        :>> interferences   = 0;
        :>> functionalFails = 0;
    }

    analysis camPinTrade : TradeStudy {
        doc /* Maximize the minimum stress margin; infeasible alternatives score -1. */
        subject :>> studyAlternatives : CinvaRam[1..*] = (v_dcam1250_tside500, v_dcam1250_tside625, v_dcam1375_tside500, v_dcam1375_tside625, v_dcam1500_tside500, v_dcam1500_tside625);
        calc :>> evaluationFunction {
            in ref :>> alternative : CinvaRam;
            return attribute :>> result : Real =
                if alternative.interferences == 0 and alternative.functionalFails == 0 and
                   alternative.peakHandleForce <= 120 [lbf]
                ? alternative.minMargin else -1.0;
        }
        objective :>> tradeStudyObjective : MaximizeObjective;
    }
}
