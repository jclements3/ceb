/* GENERATED by sysml_sync.py -- do not hand-edit
 * ceb @ 03031e0  2026-10-03T22:34Z  sweep=on
 */
package CinvaRamResults {
    private import ScalarValues::*;
    private import ISQ::*;
    private import SI::*;
    private import USCustomaryUnits::*;
    private import CinvaRamExample::*;

    part cinvaRamAnalysed :> cinvaRam {
        :>> peakHandleForce = 98.1 [lbf];     // at 150 psi
        :>> peakEjectForce  = 92.0 [lbf];
        :>> lockAngle       = 3 ['°'];
        :>> interferences   = 0;
        :>> functionalFails = 0;
        :>> minMargin       = 0.1471;
        :>> steelMass       = 281.7 [lb];
        :>> feederMass      = 52.8 [lb];
        :>> standMass       = 56.1 [lb];
        :>> heaviestPart    = 50.3 [lb];
        :>> feedCapacity    = 1499 ['in'**3];
        :>> chargeVolume    = 661.5 ['in'**3];

        // poses solved by the knee kinematics (yoke tilt, + toward fixed pins)
        attribute theta_fill : PlaneAngleValue = 32.80 ['°'];
        attribute theta_start : PlaneAngleValue = 6.37 ['°'];
        attribute theta_locked : PlaneAngleValue = -0.35 ['°'];
        attribute theta_eject : PlaneAngleValue = 80.00 ['°'];

        attribute mainPinPBending : StressCheck {
            :>> name = "Main pin P, bending"; :>> basis = "M = 24,365 lbf in, 4 webs, dia 1.750 4140";
            :>> sigma = 46308 [lbf/'in'**2]; :>> allow = 57000 [lbf/'in'**2];
        }
        attribute mainPinPShear : StressCheck {
            :>> name = "Main pin P, shear"; :>> basis = "F/2 per side";
            :>> sigma = 6234 [lbf/'in'**2]; :>> allow = 38000 [lbf/'in'**2];
        }
        attribute pinQBending : StressCheck {
            :>> name = "Pin Q, bending"; :>> basis = "M = F/2 x 0.56, dia 1.250 4140";
            :>> sigma = 43986 [lbf/'in'**2]; :>> allow = 57000 [lbf/'in'**2];
        }
        attribute camPinBending : StressCheck {
            :>> name = "Cam pin, bending"; :>> basis = "M = F/2 x 0.69, dia 1.375 4140";
            :>> sigma = 40391 [lbf/'in'**2]; :>> allow = 57000 [lbf/'in'**2];
        }
        attribute yokeArmNetTensionAtP : StressCheck {
            :>> name = "Yoke arm, net tension at P"; :>> basis = "F/2 on 0.61 sq in";
            :>> sigma = 24606 [lbf/'in'**2]; :>> allow = 29000 [lbf/'in'**2];
        }
        attribute yokeArmPinBearing : StressCheck {
            :>> name = "Yoke arm, pin bearing"; :>> basis = "F/2 on 1.75 x 0.50";
            :>> sigma = 17136 [lbf/'in'**2]; :>> allow = 32400 [lbf/'in'**2];
        }
        attribute cheekQPinBearing : StressCheck {
            :>> name = "Cheek, Q pin bearing"; :>> basis = "F/2 on 1.25 x 0.50";
            :>> sigma = 23990 [lbf/'in'**2]; :>> allow = 32400 [lbf/'in'**2];
        }
        attribute pistonWebPinBearing : StressCheck {
            :>> name = "Piston web, pin bearing"; :>> basis = "F/4 on 1.75 x 0.375";
            :>> sigma = 11424 [lbf/'in'**2]; :>> allow = 32400 [lbf/'in'**2];
        }
        attribute sidePlateBending : StressCheck {
            :>> name = "Side plate, bending"; :>> basis = "K0 0.5, band 4 in, span 14, t 0.625";
            :>> sigma = 14244 [lbf/'in'**2]; :>> allow = 23760 [lbf/'in'**2];
        }
        attribute endPlateBending : StressCheck {
            :>> name = "End plate, bending"; :>> basis = "K0 0.5, span 7 fixed ends, t 0.500";
            :>> sigma = 14994 [lbf/'in'**2]; :>> allow = 23760 [lbf/'in'**2];
        }
        attribute lidAndRampsBending : StressCheck {
            :>> name = "Lid and ramps, bending"; :>> basis = "M = F L / 8 at the scoop, I = 7.0 in^4";
            :>> sigma = 15699 [lbf/'in'**2]; :>> allow = 23760 [lbf/'in'**2];
        }
        attribute lidPlateBetweenRamps : StressCheck {
            :>> name = "Lid plate between ramps"; :>> basis = "strip span 5.62, t 0.625";
            :>> sigma = 18590 [lbf/'in'**2]; :>> allow = 23760 [lbf/'in'**2];
        }
        attribute pistonCapBending : StressCheck {
            :>> name = "Piston cap, bending"; :>> basis = "strip span 4.75, t 0.500";
            :>> sigma = 20712 [lbf/'in'**2]; :>> allow = 23760 [lbf/'in'**2];
        }
        attribute pistonWebBending : StressCheck {
            :>> name = "Piston web, bending"; :>> basis = "F/4 over 7.30, supported at the pin";
            :>> sigma = 1438 [lbf/'in'**2]; :>> allow = 23760 [lbf/'in'**2];
        }
        attribute camPinInScoopContact : StressCheck {
            :>> name = "Cam pin in scoop, contact"; :>> basis = "R 0.688 in R 0.812, AR400";
            :>> sigma = 153209 [lbf/'in'**2]; :>> allow = 241667 [lbf/'in'**2];
        }
        attribute fixedPinBendingEject : StressCheck {
            :>> name = "Fixed pin, bending (eject)"; :>> basis = "1,500 lbf per side x 1.25";
            :>> sigma = 9778 [lbf/'in'**2]; :>> allow = 33000 [lbf/'in'**2];
        }
        attribute latchHooksBearingTilting : StressCheck {
            :>> name = "Latch hooks, bearing (tilting)"; :>> basis = "2,759 lbf on 2 x 0.375 x 0.375";
            :>> sigma = 9810 [lbf/'in'**2]; :>> allow = 32400 [lbf/'in'**2];
        }
        attribute handleBendingAtTheBridge : StressCheck {
            :>> name = "Handle, bending at the bridge"; :>> basis = "200 lbf x 78.5, 2' sch 160 pipe";
            :>> sigma = 16020 [lbf/'in'**2]; :>> allow = 23100 [lbf/'in'**2];
        }
        attribute feedRailBending : StressCheck {
            :>> name = "Feed rail, bending"; :>> basis = "53 lb mid-span 10.8, 1.5 angle";
            :>> sigma = 1363 [lbf/'in'**2]; :>> allow = 23760 [lbf/'in'**2];
        }
        :>> stressChecks = (mainPinPBending, mainPinPShear, pinQBending, camPinBending, yokeArmNetTensionAtP, yokeArmPinBearing, cheekQPinBearing, pistonWebPinBearing, sidePlateBending, endPlateBending, lidAndRampsBending, lidPlateBetweenRamps, pistonCapBending, pistonWebBending, camPinInScoopContact, fixedPinBendingEject, latchHooksBearingTilting, handleBendingAtTheBridge, feedRailBending);
    }

    /* functional checks, verify() */
    attribute def CheckResult { attribute name : String; attribute ok : Boolean; attribute detail : String; }
    attribute brickThicknessAtCentre : CheckResult { :>> name = "Brick thickness at centre"; :>> ok = true; :>> detail = "4.0000 in (target 4)"; }
    attribute pistonRisesSteadilyOverTheStroke : CheckResult { :>> name = "Piston rises steadily over the stroke"; :>> ok = true; :>> detail = "-6.750 -> -4.000 in from the mold top"; }
    attribute locksOverCentreOnTheHandleRest : CheckResult { :>> name = "Locks over centre on the handle rest"; :>> ok = true; :>> detail = "at 3 deg the piston is 0.0026 in below its top point, so the brick pushes the handle onto its rest"; }
    attribute sideSlotsNeverOpenToTheSoil : CheckResult { :>> name = "Side slots never open to the soil"; :>> ok = true; :>> detail = "slot top -7.062, loose fill bottom -6.750 from mold top"; }
    attribute yokeRestsOnTheFixedPinsToFillAndEject : CheckResult { :>> name = "Yoke rests on the fixed pins to fill and eject"; :>> ok = true; :>> detail = "fill 32.8 deg, eject 80.0 deg"; }
    attribute ejectGripStaysAboveTheGround : CheckResult { :>> name = "Eject grip stays above the ground"; :>> ok = true; :>> detail = "grip 93 in -> 21 in above the ground"; }
    attribute ejectHandForce : CheckResult { :>> name = "Eject hand force"; :>> ok = true; :>> detail = "92 lbf at 1,000 lbf to break the brick loose (the piston travels 2.75 in free before it reaches the brick)"; }
    attribute camPinRidesOverTheRampIntoTheScoopWhenTheYokeStandsUp : CheckResult { :>> name = "Cam pin rides over the ramp into the scoop when the yoke stands up"; :>> ok = true; :>> detail = "piston lifts 0.829 in as the pin climbs out of / into the scoop"; }
    attribute moldCavityClearStart : CheckResult { :>> name = "Mold cavity clear (start)"; :>> ok = true; :>> detail = "nothing inside the mold"; }
    attribute moldCavityClearLocked : CheckResult { :>> name = "Mold cavity clear (locked)"; :>> ok = true; :>> detail = "nothing inside the mold"; }
    attribute allPositionsAndMotionsClear : CheckResult { :>> name = "All positions and motions clear"; :>> ok = true; :>> detail = "clear"; }
    attribute brickRisesOutOfTheMoldUnobstructed : CheckResult { :>> name = "Brick rises out of the mold unobstructed"; :>> ok = true; :>> detail = "clear at every step"; }
    attribute brickFullyAboveTheMoldAtEject : CheckResult { :>> name = "Brick fully above the mold at eject"; :>> ok = true; :>> detail = "brick bottom +0.125 from mold top"; }
    attribute brickLiftsStraightOff18In : CheckResult { :>> name = "Brick lifts straight off (18 in)"; :>> ok = true; :>> detail = "clear"; }
    attribute feedBoxHoldsAFullCharge : CheckResult { :>> name = "Feed box holds a full charge"; :>> ok = true; :>> detail = "1,499 cu in above the gate = 2.27 loose charges of 662"; }
    attribute feedBoxStopsSquareOverTheMold : CheckResult { :>> name = "Feed box stops square over the mold"; :>> ok = true; :>> detail = "lug lands on the post at y -4.375; box inside 0..14 = the mold; tails 2.01 in between the rails at full stroke"; }
    attribute knifeGateOpensTheMold : CheckResult { :>> name = "Knife gate opens the mold"; :>> ok = true; :>> detail = "open, the gate edge is 0.188 in short of the mold's far wall"; }
    attribute feedBoxSlidesAndOpensClearFill : CheckResult { :>> name = "Feed box slides and opens clear (fill)"; :>> ok = true; :>> detail = "clear at every step"; }
    attribute feedBoxRunningClearanceToTheHeadAndYoke : CheckResult { :>> name = "Feed box running clearance to the head and yoke"; :>> ok = true; :>> detail = "min 0.357 in, fbstrike to cheek at feed 1.00 (need 0.25)"; }

    satisfy CinvaRamExample::brickSize by cinvaRamAnalysed;
    satisfy CinvaRamExample::handleForce by cinvaRamAnalysed;
    satisfy CinvaRamExample::lock by cinvaRamAnalysed;
    satisfy CinvaRamExample::strength by cinvaRamAnalysed;
    satisfy CinvaRamExample::noCollision by cinvaRamAnalysed;
    satisfy CinvaRamExample::handling by cinvaRamAnalysed;
    satisfy CinvaRamExample::stresses by cinvaRamAnalysed;
    satisfy CinvaRamExample::feedCap by cinvaRamAnalysed;
}
